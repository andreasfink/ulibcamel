-- BasicGapCriteria notes: not recursive, exported,
-- locally refd 2 times, import refd 0 times
BasicGapCriteria ::= CHOICE
{
    calledAddressValue       [0] Digits,
    gapOnService             [2] GapOnService,
    calledAddressAndService  [29]   SEQUENCE
    {
        calledAddressValue [0] Digits,
        serviceKey         [1] ServiceKey,
        ...
    },
    callingAddressAndService [30]   SEQUENCE
    {
        callingAddressValue [0] Digits,
        serviceKey          [1] ServiceKey,
        ...
    }
}
-- Both calledAddressValue and callingAddressValue can be
-- incomplete numbers, in the sense that a limited amount of digits can be given.
-- For the handling of numbers starting with the same digit string refer to the detailed
-- procedure of the CallGap operation
