-- QualityOfService notes: not recursive, exported,
-- locally refd 5 times, import refd 0 times
QualityOfService ::=
 SEQUENCE
{
	requested-QoS						[0]	GPRS-QoS								OPTIONAL,
	subscribed-QoS						[1]	GPRS-QoS								OPTIONAL,
	negotiated-QoS						[2]	GPRS-QoS								OPTIONAL,
	...,
	requested-QoS-Extension				[3]	GPRS-QoS-Extension						OPTIONAL,
	subscribed-QoS-Extension			[4]	GPRS-QoS-Extension						OPTIONAL,
	negotiated-QoS-Extension			[5]	GPRS-QoS-Extension						OPTIONAL
}
