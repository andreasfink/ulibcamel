InitialDPArg ::=

SEQUENCE
{
    serviceKey                      [0]  ServiceKey,
    calledPartyNumber               [2]  CalledPartyNumber              OPTIONAL,
    callingPartyNumber              [3]  CallingPartyNumber             OPTIONAL,
    callingPartysCategory           [5]  CallingPartysCategory          OPTIONAL,
    cGEncountered                   [7]  CGEncountered                  OPTIONAL,
    iPSSPCapabilities               [8]  IPSSPCapabilities              OPTIONAL,
    locationNumber                  [10] LocationNumber                 OPTIONAL,
    originalCalledPartyID           [12] OriginalCalledPartyID          OPTIONAL,
    extensions                      [15] ExtensionsArray                OPTIONAL,
    highLayerCompatibility          [23] HighLayerCompatibility         OPTIONAL,
    additionalCallingPartyNumber    [25] AdditionalCallingPartyNumber   OPTIONAL,
    bearerCapability                [27] BearerCapability               OPTIONAL,
    eventTypeBCSM                   [28] EventTypeBCSM                  OPTIONAL,
    redirectingPartyID              [29] RedirectingPartyID             OPTIONAL,
    redirectionInformation          [30] RedirectionInformation         OPTIONAL,
    cause                           [17] Cause                          OPTIONAL,
    serviceInteractionIndicatorsTwo [32] ServiceInteractionIndicatorsTwo OPTIONAL,
    carrier                         [37] Carrier                        OPTIONAL,
    cug-Index                       [45] CUG-Index                      OPTIONAL,
    cug-Interlock                   [46] CUG-Interlock                  OPTIONAL,
    cug-OutgoingAccess              [47] NULL                           OPTIONAL,
    iMSI                            [50] IMSI                           OPTIONAL,
    subscriberState                 [51] SubscriberState                OPTIONAL,
    locationInformation             [52] LocationInformation            OPTIONAL,
    ext-basicServiceCode            [53] Ext-BasicServiceCode           OPTIONAL,
    callReferenceNumber             [54] CallReferenceNumber            OPTIONAL,
    mscAddress                      [55] ISDN-AddressString             OPTIONAL,
    calledPartyBCDNumber            [56] CalledPartyBCDNumber           OPTIONAL,
    timeAndTimezone                 [57] TimeAndTimezone                OPTIONAL,
    gsm-ForwardingPending           [58] NULL                           OPTIONAL,
    initialDPArgExtension           [59] InitialDPArgExtension          OPTIONAL,
    ...
}
