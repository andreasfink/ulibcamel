-- DpSpecificCriteria notes: not recursive, exported,
-- locally refd 1 times, import refd 0 times
DpSpecificCriteria ::= CHOICE
{
	applicationTimer					[1] ApplicationTimer,
	midCallControlInfo					[2]	MidCallControlInfo, 
	dpSpecificCriteriaAlt				[3] DpSpecificCriteriaAlt
}
