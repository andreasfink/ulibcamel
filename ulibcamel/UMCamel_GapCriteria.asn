-- GapCriteria notes: not recursive, exported,
-- locally refd 2 times, import refd 0 times
GapCriteria ::= CHOICE
{
    basicGapCriteria		BasicGapCriteria,
    compoundGapCriteria		CompoundCriteria
}
