-- InitialDPSMSArg notes: not recursive, exported,
-- locally refd 1 times, import refd 0 times
InitialDPSMSArg ::=

 SEQUENCE
{
    serviceKey                          [0]  ServiceKey,
    destinationSubscriberNumber         [1]  CalledPartyBCDNumber           OPTIONAL,
    callingPartyNumberas                [2]  SMS-AddressString              OPTIONAL,
    eventTypeSMS                        [3]  EventTypeSMS                   OPTIONAL,
    iMSI                                [4]  IMSI                           OPTIONAL,
    locationInformationMSC              [5]  LocationInformation            OPTIONAL,
    locationInformationGPRS             [6]  LocationInformationGPRS        OPTIONAL,
    sMSCAddress                         [7]  ISDN-AddressString             OPTIONAL,
    timeAndTimezone                     [8]  TimeAndTimezone                OPTIONAL,
    tPShortMessageSpecificInfo			[9]  TPShortMessageSpecificInfo     OPTIONAL,
    tPProtocolIdentifier                [10] TPProtocolIdentifier           OPTIONAL,
    tPDataCodingScheme                  [11] TPDataCodingScheme             OPTIONAL,
    tPValidityPeriod                    [12] TPValidityPeriod               OPTIONAL,
    extensions                          [13] ExtensionsArray                OPTIONAL,
	...,
    smsReferenceNumber                  [14] CallReferenceNumber            OPTIONAL,
    mscAddress                          [15] ISDN-AddressString             OPTIONAL,
    sgsnNumber                          [16] ISDN-AddressString             OPTIONAL,
	ms-Classmark2						[17] MS-Classmark2                  OPTIONAL,
	gPRSMSClass 						[18] GPRSMSClass                    OPTIONAL,
	iMEI								[19] IMEI                           OPTIONAL,
	calledPartyNumberSMS				[20] ISDN-AddressString             OPTIONAL
}
