-- Indicates the EndUserAddress, refer to 3GPP TS 29.060 for the encoding.
-- The pDPTypeOrganization shall use the least significant 4 bits of the octet encoded. 
-- The sender of this parameter shall set the most significant 4 bits of the octet to 1. 
-- The receiver of this parameter shall ignore the most significant 4 bits of this octet. 
-- Not used anymore, replaced by PDPType
-- EndUserAddress ::= SEQUENCE
-- {
--    pDPTypeOrganization [0] OCTET STRING (SIZE (1)),
--    pDPTypeNumber		[1] OCTET STRING (SIZE (1)),
--    pDPAddress			[2] OCTET STRING (SIZE (cAPSpecificBoundSetminPDPAddressLength..cAPSpecificBoundSetmaxPDPAddressLength)) OPTIONAL
-- }

-- Indicates the EndUserAddress, refer to 3GPP TS 29.060 [12] for the encoding.
-- The pDPTypeOrganization shall use the least significant 4 bits of the octet encoded.
-- The sender of this parameter shall set the most significant 4 bits of the octet to 1.
-- The receiver of this parameter shall ignore the most significant 4 bits of this octet.
