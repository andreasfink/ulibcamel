ContinueWithArgumentArgExtension ::= SEQUENCE {
	suppress-D-CSI						[0]	NULL									OPTIONAL,
	suppress-N-CSI						[1]	NULL									OPTIONAL,
	suppressOutgoingCallBarring			[2]	NULL									OPTIONAL,
	legOrCallSegment					[3]	LegOrCallSegment						OPTIONAL,
	...
	}
