-- ChargingResult notes: not recursive, exported,
-- locally refd 1 times, import refd 0 times
ChargingResult ::= CHOICE
{
    transferredVolume [0] TransferredVolume,
    elapsedTime       [1] ElapsedTime
}
