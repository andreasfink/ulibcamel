-- AOCBeforeAnswer notes: not recursive, exported,
-- locally refd 1 times, import refd 0 times

AOCBeforeAnswer ::= SEQUENCE
{
    aOCInitial    [0] CAI-Gsm0224,
    aOCSubsequent [1] AOCSubsequent OPTIONAL
}
