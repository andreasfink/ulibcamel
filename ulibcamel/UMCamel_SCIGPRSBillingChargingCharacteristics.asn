-- SCIGPRSBillingChargingCharacteristics notes: not recursive, exported,
-- locally refd 2 times, import refd 0 times
SCIGPRSBillingChargingCharacteristics ::=

OCTET STRING (SIZE (cAPSpecificBoundSetminSCIBillingChargingLength ..cAPSpecificBoundSetmaxSCIBillingChargingLength ))
