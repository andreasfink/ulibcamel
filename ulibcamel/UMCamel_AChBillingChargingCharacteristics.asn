-- AChBillingChargingCharacteristics notes: not recursive, exported,
-- locally refd 2 times, import refd 0 times
AChBillingChargingCharacteristics ::= CHOICE
{
    actimeDurationCharging [0]   AChTimeDuration Charging
}
