-- GPRSEventSpecificInformation notes: not recursive, exported,
-- locally refd 2 times, import refd 0 times
GPRSEventSpecificInformation ::= CHOICE
{
    attachChangeOfPositionSpecificInformation [0]  SEQUENCE
    {
        locationInformationGPRS [0] LocationInformationGPRS OPTIONAL,
		...
    },
    pdp-ContextchangeOfPositionSpecificInformation [1]  SEQUENCE
    {
        accessPointName         [0] AccessPointName         OPTIONAL,
        chargingID              [1] GPRSChargingID          OPTIONAL,
        locationInformationGPRS [2] LocationInformationGPRS OPTIONAL,
        pDPType                 [3] PDPType                 OPTIONAL,
        qualityOfService        [4] QualityOfService        OPTIONAL,
        timeAndTimeZone         [5] TimeAndTimezone         OPTIONAL,
		...,
        gGSNAddress             [6] GSN-Address              OPTIONAL
    },
    detachSpecificInformation [2]  SEQUENCE
    {
        inititatingEntity       [0] InitiatingEntity        OPTIONAL,
		...,
        routeingAreaUpdate      [1] NULL                    OPTIONAL
    },
    disconnectSpecificInformation [3]  SEQUENCE
    {
        inititatingEntity       [0] InitiatingEntity        OPTIONAL,
		...,
        routeingAreaUpdate      [1] NULL                    OPTIONAL
    },
    pDPContextEstablishmentSpecificInformation [4]  SEQUENCE
    {
        accessPointName         [0] AccessPointName         OPTIONAL,
        pDPType                 [1] PDPType                 OPTIONAL,
        qualityOfService        [2] QualityOfService        OPTIONAL,
        locationInformationGPRS [3] LocationInformationGPRS OPTIONAL,
        timeAndTimeZone         [4] TimeAndTimezone         OPTIONAL,
        pDPInitiationType       [5] PDPInitiationType       OPTIONAL,
		...,
        secondaryPDPContext     [6] NULL                    OPTIONAL
    },
    pDPContextEstablishmentAcknowledgementSpecificInformation [5] SEQUENCE
    {
        accessPointName         [0] AccessPointName         OPTIONAL,
        chargingID              [1] GPRSChargingID          OPTIONAL,
        pDPType                 [2] PDPType                 OPTIONAL,
        qualityOfService        [3] QualityOfService        OPTIONAL,
        locationInformationGPRS [4] LocationInformationGPRS OPTIONAL,
        timeAndTimeZone         [5] TimeAndTimezone         OPTIONAL,
		...,
        gGSNAddress             [6] GSN-Address              OPTIONAL
    }
}
