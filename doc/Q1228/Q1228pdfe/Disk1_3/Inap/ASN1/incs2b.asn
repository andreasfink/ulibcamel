INCS2BundleArg {ccitt recommendation q 1228 modules(0) in-cs2-ssf-scf-ops-args (5) version1(0)}
DEFINITIONS IMPLICIT TAGS ::= 
BEGIN
IMPORTS

CancelFailed,
RequestedInfoError,
SystemFailure,
TaskRefused,
ActivateServiceFilteringArg, 
ApplyChargingArg ,
ApplyChargingReportArg ,
AssistRequestInstructionsArg ,
CallGapArg ,
CallInformationReportArg ,
CallInformationRequestArg , 
CancelArg ,
CancelStatusReportRequestArg ,
CollectInformationArg ,
ConnectArg ,
ConnectToResourceArg,
ContinueWithArgumentArg ,
CreateCallSegmentAssociationArg ,
CreateCallSegmentAssociationResultArg ,
DisconnectForwardConnectionWithArgumentArg ,
DisconnectLegArg ,
EntityReleasedArg , 
EstablishTemporaryConnectionArg ,
EventNotificationChargingArg ,
EventReportBCSMArg ,
FurnishChargingInformationArg ,
InitialDPArg ,
InitiateCallAttemptArg ,
ManageTriggerDataArg , 
ManageTriggerDataResultArg  ,
MergeCallSegmentsArg ,
MoveCallSegmentsArg ,
MoveLegArg ,
ReleaseCallArg ,
ReportUTSIArg ,
RequestCurrentStatusReportArg ,
RequestCurrentStatusReportResultArg ,
RequestEveryStatusChangeReportArg ,
RequestFirstStatusMatchReportArg ,
RequestReportBCSMEventArg , 
RequestReportUTSIArg ,
ResetTimerArg ,
SendChargingInformationArg ,
SendSTUIArg ,
ServiceFilteringResponseArg ,
SplitLegArg ,
StatusReportArg 

FROM INCS2SSFSCFopsargs


;

Empty	::= NULL

ArgType ::= CHOICE	
	{	aSFArg 		ActivateServiceFilteringArg,
		aSF_RArg	Empty,
                aTArg           Empty,
                aT_RArg         Empty,
		aCArg		ApplyChargingArg ,
		aCRArg		ApplyChargingReportArg ,
		aRIArg		AssistRequestInstructionsArg ,
		cGArg		CallGapArg ,
		cIRArg		CallInformationReportArg ,
		cIRQArg		CallInformationRequestArg , 
		cANArg		CancelArg ,
		cIArg		CollectInformationArg ,
		cONArg		ConnectArg ,
		cTRArg		ConnectToResourceArg,
		cWAArg		ContinueWithArgumentArg ,
		cSAArg		CreateCallSegmentAssociationArg ,
		cSA_RArg	CreateCallSegmentAssociationResultArg ,
                cUEArg          Empty,
		dFCWAArg	DisconnectForwardConnectionWithArgumentArg ,
		dLArg		DisconnectLegArg ,
		dL_RArg		Empty,
		eRArg		EntityReleasedArg , 
		eTCArg		EstablishTemporaryConnectionArg ,
		eNCArg		EventNotificationChargingArg ,
		eRBArg		EventReportBCSMArg ,
		fCIArg		FurnishChargingInformationArg ,
		iDPArg		InitialDPArg ,
		iCAArg		InitiateCallAttemptArg ,
		mTDArg		ManageTriggerDataArg , 
		mTD_RArg	ManageTriggerDataResultArg,
		mCArg		MergeCallSegmentsArg,
		mC_RArg		Empty,
		mCSArg		MoveCallSegmentsArg,
		mCS_RArg	Empty,
		mLArg		MoveLegArg,
		mL_RArg		Empty,
		rCArg		ReleaseCallArg ,
		rUArg		ReportUTSIArg ,
		rNCArg		RequestNotificationChargingEventArg , 
		rRBArg		RequestReportBCSMEventArg , 
		rRUArg		RequestReportUTSIArg ,
		rTArg		ResetTimerArg ,
		sCIArg		SendChargingInformationArg ,
		sSArg		SendSTUIArg ,
		sFRArg		ServiceFilteringResponseArg ,
		sLArg		SplitLegArg ,
		sL_RArg		Empty
	}

ErrorType ::= CHOICE	
	{	cancelPar			Empty,
		cancelFailedPar			CancelFailed,
		chainingRefusedPar		Empty,
		eTCFailedPar			Empty,
		improperCallerResponsePar	Empty,
		missingCustomerRecordPar	Empty,
		missingParameterPar		Empty,
		parameterOutOfRangePar		Empty,
		requestedInfoError		RequestedInfoError,
		systemFailurePar		SystemFailure,
		taskRefusedPar			TaskRefused,	
		unavailableResourcePar		Empty,
		unexpectedComponentSequencePar	Empty,
		unexpectedDataValuePar		Empty,
		unexpectedParameterPar		Empty,
		unknownLegIDPar			Empty,
		unknownRecordedMessageID	Empty,
		unknownResource			Empty,
		unknownSubscriber		Empty	
	}
END
